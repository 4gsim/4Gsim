Internode-definitions DEFINITIONS AUTOMATIC TAGS ::=

IMPORTS

-- Core Network IEs :
	CN-DomainIdentity,
	CN-InformationInfo,
	CN-InformationInfo-r6,
	CN-InformationInfoFull,
	NAS-Message,
	PagingRecordTypeID,
	PLMN-Identity,
-- UTRAN Mobility IEs :
	CellIdentity,
	CellIdentity-PerRL-List,
	DedicatedPriorityInformation,
	URA-Identity,
-- User Equipment IEs :
	AccessStratumReleaseIndicator,
	ActivationTime,
	C-RNTI,
	CapabilityUpdateRequirement,
	CapabilityUpdateRequirement-r4,
	CapabilityUpdateRequirement-r4-ext,
	CapabilityUpdateRequirement-r5,
	CapabilityUpdateRequirement-v770ext,
	CapabilityUpdateRequirement-v860ext,
	CapabilityUpdateRequirement-r7,
	CapabilityUpdateRequirement-r8,
	CellUpdateCause,
	CellUpdateCause-ext,
	CipheringAlgorithm,
	CipheringAlgorithm-r7,
	CipheringModeInfo,
	CipheringModeInfo-r7,
	DelayRestrictionFlag,
	DL-PhysChCapabilityFDD-v380ext,
	DSCH-RNTI,
	E-RNTI,
	EstablishmentCause,
	FailureCauseWithProtErr,
	FailureCauseWithProtErrTrId,
	GroupReleaseInformation,
	H-RNTI,
	High-MobilityDetected,
	InitialUE-Identity,
	IntegrityProtActivationInfo,
	IntegrityProtectionModeInfo,
	IntegrityProtectionModeInfo-r7,
	N-308,
	PagingCause,
	PagingRecordList,
	PagingRecord2List-r5,
	PDCP-Capability-r4-ext,
	PDCP-Capability-v770ext,
	Pre-RedirectionInfo,
	ProtocolErrorIndicator,
	ProtocolErrorIndicatorWithMoreInfo,
	RadioFrequencyBandTDDList,
	Rb-timer-indicator,
	RedirectionInfo,
	RedirectionInfo-r6,
	RedirectionInfo-v860ext,
	RejectionCause,
	ReleaseCause,
	RF-CapabilityComp,
	RRC-StateIndicator,
	RRC-TransactionIdentifier,
	SecurityCapability,
	SR-VCC-Info,
	SR-VCC-SecurityRABInfo-v860ext,
	START-Value,
	STARTList,
	SystemSpecificCapUpdateReq-v590ext,
	U-RNTI,
	U-RNTI-Short,
	UESpecificBehaviourInformation1idle,
	UESpecificBehaviourInformation1interRAT,
	UE-CapabilityContainer-IEs,
	UE-ConnTimersAndConstants,
	UE-ConnTimersAndConstants-v3a0ext,
	UE-ConnTimersAndConstants-v860ext,
	UE-ConnTimersAndConstants-r5,
	UE-HSPA-Identities-r6,
	UE-RadioAccessCapabBandFDDList2,
	UE-RadioAccessCapabBandFDDList-ext,
	UE-RadioAccessCapability,
	UE-RadioAccessCapability-v370ext,
	UE-RadioAccessCapability-v380ext,
	UE-RadioAccessCapability-v3a0ext,
	UE-RadioAccessCapability-v3g0ext,
	UE-RadioAccessCapability-v4b0ext,
	UE-RadioAccessCapability-v590ext,
	UE-RadioAccessCapability-v5c0ext,
	UE-RadioAccessCapability-v650ext,
	UE-RadioAccessCapability-v680ext,
	UE-RadioAccessCapability-v7e0ext,
	UE-RadioAccessCapability-v7f0ext,
	UE-RadioAccessCapability-v860ext,
	UE-RadioAccessCapability-v880ext,
	UE-RadioAccessCapability-v890ext,
	UE-RadioAccessCapability-v920ext,
	UE-RadioAccessCapabilityComp,
	UE-RadioAccessCapabilityComp-ext,
	UE-RadioAccessCapabilityComp-v770ext,
	UE-RadioAccessCapabilityComp2,
	UE-RadioAccessCapabilityComp2-v770ext,
	UE-RadioAccessCapabilityComp2-v7f0ext,
	UE-RadioAccessCapabilityComp2-v860ext,
	UE-RadioAccessCapabilityComp2-v920ext,
	UE-RadioAccessCapabilityComp-TDD128,
	UE-RadioAccessCapabilityInfo-v770ext,
	UE-RadioAccessCapabilityInfo-TDD128-v8b0ext,
	UE-SecurityInformation,
	UE-SecurityInformation2,
	UE-SpecificCapabilityInformation-LCRTDD,
	URA-UpdateCause,
	UTRAN-DRX-CycleLengthCoefficient,
	UTRAN-DRX-CycleLengthCoefficient-r7,
	WaitTime,
-- Radio Bearer IEs :
	DefaultConfigIdentity,
	DefaultConfigIdentity-r4,
	DefaultConfigIdentity-r5,
	DefaultConfigIdentity-r6,
	DefaultConfigForCellFACH,
	DefaultConfigMode,
	DL-CounterSynchronisationInfo,
	DL-CounterSynchronisationInfo-r5,
	PDCP-ROHC-TargetMode,
	PredefinedConfigIdentity,
	PredefinedConfigStatusList,
	PredefinedConfigStatusListComp,
	PredefinedConfigSetWithDifferentValueTag,
	RAB-Info,
	RAB-Info-r6,
	RAB-Info-r7,
	RAB-Info-Post,
	RAB-InformationList,
	RAB-InformationList-r6,
	RAB-InformationReconfigList,
	RAB-InformationReconfigList-r8,
	RAB-InformationMBMSPtpList,
	RAB-InformationSetup-r7,
	RAB-InformationSetup-r8,
	RAB-InformationSetup-v820ext,
	RAB-InformationSetupList,
	RAB-InformationSetupList-r4,
	RAB-InformationSetupList-r5,
	RAB-InformationSetupList-r6-ext,
	RAB-InformationSetupList-r6,
	RAB-InformationSetupList-v6b0ext,
	RAB-InformationSetupList-r7,
	RAB-InformationSetupList-r8,
	RAB-InformationSetupList-v820ext,
	RB-ActivationTimeInfoList,
	RB-COUNT-C-InformationList,
	RB-COUNT-C-MSB-InformationList,
	RB-IdentityList,
	RB-InformationAffectedList,
	RB-InformationAffectedList-r5,
	RB-InformationAffectedList-r6,
	RB-InformationAffectedList-r7,
	RB-InformationAffectedList-r8,
	RB-InformationChangedList-r6,
	RB-InformationReconfigList,
	RB-InformationReconfigList-r4,
	RB-InformationReconfigList-r5,
	RB-InformationReconfigList-r6,
	RB-InformationReconfigList-r7,
	RB-InformationReconfigList-r8,
	RB-InformationReleaseList,
	RB-PDCPContextRelocationList,
	SRB-InformationSetupList,
	SRB-InformationSetupList-r5,
	SRB-InformationSetupList-r6,
	SRB-InformationSetupList-r7,
	SRB-InformationSetupList-r8,
	SRB-InformationSetupList2,
	SRB-InformationSetupList2-r6,
	SRB-InformationSetupList2-r7,
	SRB-InformationSetupList2-r8,
	UL-AMR-Rate,
	UL-CounterSynchronisationInfo,
-- Transport Channel IEs:
	CPCH-SetID,
	DL-AddReconfTransChInfo2List,
	DL-AddReconfTransChInfoList,
	DL-AddReconfTransChInfoList-r4,
	DL-AddReconfTransChInfoList-r5,
	DL-AddReconfTransChInfoList-r7,
	DL-AddReconfTransChInfoList-r9,
	DL-CommonTransChInfo,
	DL-CommonTransChInfo-r4,
	DL-DeletedTransChInfoList,
	DL-DeletedTransChInfoList-r5,
	DL-DeletedTransChInfoList-r7,
	DRAC-StaticInformationList,
	HARQ-Info-r7,
	PowerOffsetInfoShort,
	TFC-Subset,
	TFCS-Identity,
	UL-AddReconfTransChInfoList,
	UL-AddReconfTransChInfoList-r6,
	UL-AddReconfTransChInfoList-r7,
	UL-AddReconfTransChInfoList-r8,
	UL-CommonTransChInfo,
	UL-CommonTransChInfo-r4,
	UL-DeletedTransChInfoList,
	UL-DeletedTransChInfoList-r6,
-- Physical Channel IEs :
	Alpha,
	BEACON-PL-Est,
	CCTrCH-PowerControlInfo,
	CCTrCH-PowerControlInfo-r4,
	CCTrCH-PowerControlInfo-r5,
	CCTrCH-PowerControlInfo-r7,
	ConstantValue,
	ConstantValueTdd,
	ControlChannelDRXInfo-TDD128-r8,
	CPCH-SetInfo,
	DHS-Sync,
	DL-CommonInformation,
	DL-CommonInformation-r4,
	DL-CommonInformation-r5,
	DL-CommonInformation-r6,
	DL-CommonInformation-r7,
	DL-CommonInformation-r8,
	DL-CommonInformationPost,
	DL-HSPDSCH-Information,
	DL-HSPDSCH-Information-r6,
	DL-HSPDSCH-Information-r7,
	DL-HSPDSCH-Information-r8,
	DL-HSPDSCH-Information-r8-ext,
	DL-HSPDSCH-Information-r9,
	DL-HSPDSCH-Information-r8-ext2,
	DL-HSPDSCH-MultiCarrier-Information,
	DL-InformationPerRL-List,
	DL-InformationPerRL-List-r4,
	DL-InformationPerRL-List-r5,
	DL-InformationPerRL-List-r5bis,
	DL-InformationPerRL-List-r6, 
	DL-InformationPerRL-List-r7,
	DL-InformationPerRL-List-r8,
	DL-InformationPerRL-List-v6b0ext,
	DL-InformationPerRL-ListPostFDD,
	DL-InformationPerRL-PostTDD,
	DL-InformationPerRL-PostTDD-LCR-r4,
	DL-MultiCarrier-Information,
	DL-PDSCH-Information,
	DL-SecondaryCellInfoFDD,
	DL-SecondaryCellInfoFDD-v890ext,
	DL-SecondaryCellInfoFDD-r9,
	DL-TPC-PowerOffsetPerRL-List,
	DLUL-HSPA-Information-r8,
	DLUL-HSPA-Information-r9,
	DPC-Mode,
	DPCH-CompressedModeStatusInfo,
	DTX-DRX-TimingInfo-r7,
	DTX-DRX-Info-r7,
	DynamicPersistenceLevel,
	E-DCH-ReconfigurationInfo,
	E-DCH-ReconfigurationInfo-SecULFrequency,
	E-DCH-ReconfigurationInfo-r7,
	E-DCH-RL-InfoSameServingCell,
	E-TFC-Boost-Info-r7,
	E-DPDCH-PowerInterpolation,
	EXT-UL-TimingAdvance,
	Feedback-cycle-r7,
	FrequencyInfo,
	FrequencyInfoFDD,
	FrequencyInfoTDD,
	HARQ-Preamble-Mode,
	HS-DSCH-TBSizeTable,
	HS-SCCH-LessInfo-r7,
	HS-SICH-Power-Control-Info-TDD384,
	HS-SICH-Power-Control-Info-TDD768,
	MaxAllowedUL-TX-Power,
	MIMO-Parameters-r7,
	MIMO-Parameters-v7f0ext,
	MIMO-Parameters-v7g0ext,
	MIMO-Parameters-r8,
	MIMO-Parameters-r9,
	Multi-frequencyInfo-LCR-r7,
	OpenLoopPowerControl-IPDL-TDD-r4,
	PDSCH-CapacityAllocationInfo,
	PDSCH-CapacityAllocationInfo-r4,
	PDSCH-CapacityAllocationInfo-r7,
	PDSCH-Identity,
	PrimaryCPICH-Info,
	PrimaryCCPCH-TX-Power,
	PUSCH-CapacityAllocationInfo,
	PUSCH-CapacityAllocationInfo-r4, 
	PUSCH-CapacityAllocationInfo-r7,
	PUSCH-Identity,
	PUSCH-SysInfoList-HCR-r5,
	PDSCH-SysInfoList-HCR-r5,
	RL-AdditionInformationList,
	RL-AdditionInformationList-r6,
	RL-AdditionInformation-list-v6b0ext,
	RL-AdditionInformationList-r7,
	RL-AdditionInformationList-r8,
	RL-AdditionInformationList-v890ext,
	RL-AdditionInformationList-r9,
	RL-AdditionInformationList-v950ext,
	RL-AdditionInformationList-SecULFreq,
	RL-RemovalInformationList,
	RL-RemovalInformationList-SecULFreq,
	SecondaryCellMIMOparametersFDD-v950ext,
	Serving-HSDSCH-CellInformation,
	Serving-HSDSCH-CellInformation-r7,
	Serving-HSDSCH-CellInformation-r8,
	Serving-HSDSCH-CellInformation-r9,
	ServingCellChangeParameters,
	SpecialBurstScheduling,
	SPS-Information-TDD128-r8,
	SSDT-Information,
	SSDT-Information-r4,
	SSDT-UL,
	TFC-ControlDuration,
	TimeslotList,
	TimeslotList-r4,
	TimingMaintainedSynchInd,
	TX-DiversityMode,
	UL-16QAM-Config,
	UL-ChannelRequirement,
	UL-ChannelRequirement-r4,
	UL-ChannelRequirement-r5,
	UL-ChannelRequirementWithCPCH-SetID,
	UL-ChannelRequirementWithCPCH-SetID-r4,
	UL-ChannelRequirementWithCPCH-SetID-r5,
	UL-DPCH-Info,
	UL-DPCH-Info-r4, 
	UL-DPCH-Info-r5,
	UL-DPCH-Info-r6,
	UL-DPCH-Info-r7,
	UL-DPCH-InfoPostFDD,
	UL-DPCH-InfoPostTDD,
	UL-DPCH-InfoPostTDD-LCR-r4,
	UL-EDCH-Information-ext,
	UL-EDCH-Information-r6,
	UL-EDCH-Information-r7,
	UL-EDCH-Information-r8,
	UL-EDCH-Information-r9,
	UL-SecondaryCellInfoFDD,
	UL-SynchronisationParameters-r4,
	UL-TimingAdvance,
	UL-TimingAdvanceControl,
	UL-TimingAdvanceControl-r4,
	UL-TimingAdvanceControl-r7,
	UpPCHposition-LCR,
-- Measurement IEs :
	AdditionalMeasurementID-List,
	CellDCHMeasOccasionInfo-TDD128-r9,
	CSGProximityIndication,
	DeltaRSCP,
	Frequency-Band,
	EventResults,
	EventResults-v770ext,
	EventResults-v860ext,
	EventResultsOnSecUlFreq,
	EUTRA-EventResults,
	EUTRA-MeasuredResults,
	EUTRA-MeasuredResults-v920ext,
	Inter-FreqEventCriteriaList-v590ext,
	Intra-FreqEventCriteriaList-v590ext,
	IntraFreqReportingCriteria-1b-r5,
	IntraFreqEvent-1d-r5,
	IntraFreqCellID,
	InterFreqEventResults-LCR-r4-ext,
	InterRATCellInfoIndication,
	InterRAT-TargetCellDescription,
	MeasuredResults,
	MeasuredResults-v390ext,
	MeasuredResults-v590ext,
	MeasuredResults-v770ext,
	MeasuredResults-v860ext,
	MeasuredResults-v920ext,
	MeasuredResultsOnSecUlFreq,
	MeasuredResultsListOnSecUlFreq,
	MeasuredResultsList,
	MeasuredResultsList-LCR-r4-ext,
	MeasuredResultsList-v770xet,
	MeasuredResultsList-v860ext,
	MeasuredResultsList-v920ext,
	MeasuredResultsOnRACH,
	MeasuredResultsOnRACH-v7g0ext,
	MeasuredResultsOnRACHinterFreq,
	MeasurementCommand,
	MeasurementCommand-r4,
	MeasurementCommand-r6,
	MeasurementCommand-r7,
	MeasurementCommand-r8,
	MeasurementCommand-r9,
	MeasurementIdentity,
	MeasurementReportingMode,
	NewInterFreqCellList-v7b0ext,
	NewInterFreqCellList-LCR-v8a0ext,
	NewIntraFreqCellList-LCR-v8a0ext,
	PrimaryCCPCH-RSCP,
	SFN-Offset-Validity,
	TimeslotListWithISCP,
	TrafficVolumeMeasuredResultsList,
	UE-Positioning-GPS-AssistanceData,
	UE-Positioning-GPS-AssistanceData-v770ext,
	UE-Positioning-GPS-AssistanceData-v920ext,
	UE-Positioning-GPS-ReferenceTimeUncertainty,
	UE-Positioning-Measurement-v390ext,
	UE-Positioning-Measurement-v920ext,
	UE-Positioning-OTDOA-AssistanceData,
	UE-Positioning-OTDOA-AssistanceData-r4ext,
	UE-Positioning-OTDOA-AssistanceData-UEB,
	UE-Positioning-OTDOA-AssistanceData-UEB-ext,
	UE-Positioning-OTDOA-MeasuredResultsTDD-ext,
	UE-Positioning-GANSS-AssistanceData,
	UE-Positioning-GANSS-AssistanceData-v860ext,
	UE-Positioning-GANSS-AssistanceData-v920ext,
-- Other IEs :
	BCCH-ModificationInfo,
	CDMA2000-MessageList,
	ETWS-Information,
	ETWS-WarningSecurityInfo,
	GSM-TargetCellInfoList,
	GERANIu-MessageList,
	GERAN-SystemInformation,
	GSM-MessageList,
	InterRAT-ChangeFailureCause,
	InterRAT-HO-FailureCause,
	InterRAT-UE-RadioAccessCapabilityList,
	InterRAT-UE-RadioAccessCapability-v590ext,
	InterRAT-UE-SecurityCapList,
	IntraDomainNasNodeSelector,
	MasterInformationBlock,
	MIB-ValueTag,
	ProtocolErrorMoreInformation,
	Rplmn-Information,
	Rplmn-Information-r4,
	SegCount,
	SegmentIndex,
	SFN-Prime,
	SIB-Data-fixed,
	SIB-Data-variable,
	SIB-Type,
	SysInfoType1,
	SysInfoType3,
	SysInfoType5,
	SysInfoType7,
	SysInfoType11,
	SysInfoType11bis,
	SysInfoType12,
	SysInfoTypeSB1,
	SysInfoTypeSB2,
-- MBMS IEs:
	MBMS-CellGroupIdentity-r6,
	MBMS-CommonRBInformationList-r6,
	MBMS-CurrentCell-SCCPCHList-r6,
	MBMS-JoinedInformation-r6,
	MBMS-MICHConfigurationInfo-r6,
	MBMS-MICHConfigurationInfo-v770ext,
	MBMS-MICHConfigurationInfo-v890ext,
	MBMS-ModifedServiceList-r6,
	MBMS-ModifiedServiceList-LCR-v7c0ext,
	MBMS-ModifiedServiceList-v770ext,
	MBMS-MSCH-ConfigurationInfo-r6,
	MBMS-NeighbouringCellSCCPCHList-r6,
	MBMS-NeighbouringCellSCCPCHList-v770ext,
	MBMS-NumberOfNeighbourCells-r6,
	MBMS-PhyChInformationList-r6,
	MBMS-PhyChInformationList-r7,
	MBMS-PhyChInformationList-IMB384,
	MBMS-PL-ServiceRestrictInfo-r6,
	MBMS-PreferredFrequencyList-r6,
	MBMS-PTMActivationTime-r6,
	MBMS-SelectedServiceInfo,
	MBMS-SelectedServicesShort,
	MBMS-ServiceAccessInfoList-r6,
	MBMS-ServiceIdentity-r6,
	MBMS-ServiceSchedulingInfoList-r6,
	MBMS-SIBType5-SCCPCHList-r6,
	MBMS-TimersAndCounters-r6,
	MBMS-TranspChInfoForEachCCTrCh-r6,
	MBMS-TranspChInfoForEachTrCh-r6,
	MBMS-UnmodifiedServiceList-r6,
	MBMS-UnmodifiedServiceList-v770ext,
	MBSFN-ClusterFrequency-r7,
	MBSFN-InterFrequencyNeighbourList-r7,
	MBSFN-InterFrequencyNeighbourList-v860ext,
	MBMS-NetworkStandardTimeInformation-LCR-v890ext,
	MBSFN-TDDInformation-LCR,
	MBSFN-TDM-Info-List
FROM InformationElements

	maxSIBperMsg,
	maxURNTI-Group
FROM Constant-definitions;

-- ***************************************************
--
-- MBMS CURRENT CELL PTM RB INFORMATION
--
-- ***************************************************

Digit ::=							INTEGER (0..9)

MCC ::=								SEQUENCE (SIZE (3)) OF
										Digit

MNC ::=								SEQUENCE (SIZE (2..3)) OF
										Digit

PLMN-Identity ::=					SEQUENCE {
	mcc									MCC,
	mnc									MNC
}

END
